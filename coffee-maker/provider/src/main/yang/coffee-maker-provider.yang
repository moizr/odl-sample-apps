module coffee-maker-provider {

    yang-version 1;
    namespace "cisco:controller:samples:config:coffee-maker-provider";
    prefix "coffee-maker-provider";

    import config { prefix config; revision-date 2013-04-05; }
    import opendaylight-md-sal-binding { prefix mdsal; revision-date 2013-10-28; }

    description
        "This module contains the base YANG definitions for
        coffee-provider impl implementation.";

    revision "2014-11-14" {
        description
            "Initial revision.";
    }

    // This is the definition of the service implementation as a module identity.
    identity coffee-maker-provider {
            base config:module-type;

            // Specifies the prefix for generated java classes.
            config:java-name-prefix CoffeemakerProvider;
    }

    // Augments the 'configuration' choice node under modules/module.
    // We consume the three main services, RPCs, DataStore, and Notifications
    augment "/config:modules/config:module/config:configuration" {
        case coffee-maker-provider {
            when "/config:modules/config:module/config:type = 'coffee-maker-provider'";

            container data-broker {
                uses config:service-ref {
                    refine type {
                        mandatory false;
                        config:required-identity mdsal:binding-async-data-broker;
                    }
                }
            }

            container rpc-registry {
                uses config:service-ref {
                    refine type {
                        mandatory true;
                        config:required-identity mdsal:binding-rpc-registry;
                    }
                }
            }

            container notification-broker {
                uses config:service-ref {
                    refine type {
                        mandatory true;
                        config:required-identity mdsal:binding-notification-service;
                    }
                }
            }

        }
    }
}
