module coffee-maker-consumer {

    yang-version 1;
    namespace "cisco:controller:samples:config:coffee-maker-consumer";
    prefix "coffee-maker-consumer";

    import config { prefix config; revision-date 2013-04-05; }
    import opendaylight-md-sal-binding { prefix mdsal; revision-date 2013-10-28; }

    description
        "This module contains the base YANG definitions for
        coffee-consumer impl implementation.";

    revision "2014-11-14" {
        description
            "Initial revision.";
    }

    // This is the definition of the service implementation as a module identity.
    identity coffee-maker-consumer {
            base config:module-type;

            // Specifies the prefix for generated java classes.
            config:java-name-prefix CoffeemakerConsumer;
    }

    // Augments the 'configuration' choice node under modules/module.
    // We consume the three main services, RPCs, DataStore, and Notifications
    augment "/config:modules/config:module/config:configuration" {
        case coffee-maker-consumer {
            when "/config:modules/config:module/config:type = 'coffee-maker-consumer'";

            container data-broker {
                uses config:service-ref {
                    refine type {
                        mandatory false;
                        config:required-identity mdsal:binding-async-data-broker;
                    }
                }
            }

            container rpc-registry {
                uses config:service-ref {
                    refine type {
                        mandatory true;
                        config:required-identity mdsal:binding-rpc-registry;
                    }
                }
            }

            container notification-broker {
                uses config:service-ref {
                    refine type {
                        mandatory true;
                        config:required-identity mdsal:binding-notification-service;
                    }
                }
            }

        }
    }
}
